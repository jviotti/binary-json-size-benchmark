GeneratedSchema DEFINITIONS AUTOMATIC TAGS ::= BEGIN
Rule ::= SEQUENCE {
    kind CHOICE {
        level INTEGER,
        when UTF8String,
        options SEQUENCE OF UTF8String
    }
}
Rules ::= SEQUENCE {
    scopeCase SEQUENCE OF Rule,
    subjectCase SEQUENCE OF Rule
}
Main ::= SEQUENCE {
    rules Rules
}
END
