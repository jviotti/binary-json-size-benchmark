GeneratedSchema DEFINITIONS AUTOMATIC TAGS ::= BEGIN
Let ::= SEQUENCE {
    x SEQUENCE OF INTEGER (0..MAX)
}
Sort ::= SEQUENCE {
    eval UTF8String
}
Reverse ::= SEQUENCE {
    sort Sort,
    byX UTF8String
}
In ::= SEQUENCE {
    reverse Reverse
}
Main ::= SEQUENCE {
    let Let,
    in In
}
END
