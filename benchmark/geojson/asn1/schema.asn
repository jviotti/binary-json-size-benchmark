GeneratedSchema DEFINITIONS AUTOMATIC TAGS ::= BEGIN
Coordinates3 ::= SEQUENCE {
    coordinates SEQUENCE OF REAL
}
Coordinates2 ::= SEQUENCE {
    coordinates SEQUENCE OF Coordinates3
}
Coordinates1 ::= SEQUENCE {
    coordinates SEQUENCE OF Coordinates2
}
Main ::= SEQUENCE {
    type UTF8String,
    coordinates SEQUENCE OF Coordinates1
}
END
