GeneratedSchema DEFINITIONS AUTOMATIC TAGS ::= BEGIN
ComplexRule ::= SEQUENCE {
    kind CHOICE {
        textual UTF8String,
        options SEQUENCE OF UTF8String,
        booleanOptions SEQUENCE OF BOOLEAN
    }
}
Rules ::= SEQUENCE {
    -- TODO: Use ENUMERATED for these string values
    requireAuthor UTF8String,
    requireDescription UTF8String,
    requireEngines UTF8String,
    requireLicense UTF8String,
    requireName UTF8String,
    requireRepository UTF8String,
    requireVersion UTF8String,
    requireBugs UTF8String,
    requireHomepage UTF8String,
    requireKeywords UTF8String,
    binType UTF8String,
    configType UTF8String,
    descriptionType UTF8String,
    devDependenciesType UTF8String,
    directoriesType UTF8String,
    enginesType UTF8String,
    filesType UTF8String,
    homepageType UTF8String,
    keywordsType UTF8String,
    licenseType UTF8String,
    mainType UTF8String,
    manType UTF8String,
    nameType UTF8String,
    preferGlobalType UTF8String,
    privateType UTF8String,
    repositoryType UTF8String,
    scriptsType UTF8String,
    versionType UTF8String,
    validValuesAuthor SEQUENCE OF ComplexRule,
    validValuesPrivate SEQUENCE OF ComplexRule,
    noRestrictedDependencies SEQUENCE OF ComplexRule,
    noRestrictedPreReleaseDependencies SEQUENCE OF ComplexRule,
    noRestrictedInvalidDevDependencies SEQUENCE OF ComplexRule,
    noRestrictedPreReleaseDevDependencies SEQUENCE OF ComplexRule,
    nameFormat UTF8String,
    versionFormat UTF8String
}
Main ::= SEQUENCE {
    rules Rules
}
END
